FME workspace Rastry.fmw

Parameters:
- SourceDataset_PATH = C:\Users\Kacper.Sobczyk\Downloads\datasets   # INCLUDE_WEB_BROWSER Source Folder and File Pathnames Folder
- DestDataset_CSV2 = C:\Users\Kacper.Sobczyk\Documents   # Destination CSV (Comma Separated Value) Folder
- SourceDataset_CSV2 = $(FME_MF_DIR)final_results\data_winter_low_results.csv   # Source CSV (Comma Separated Value) File(s)
- DestDataset_GEODATABASE_FILE_RASTER_DATASET = $(FME_MF_DIR)RasterData.gdb   # File Geodatabase

Readers:
- PATH_1: PATH from $(SourceDataset_PATH)
- CSV2_2: CSV2 from $(SourceDataset_CSV2)

Writers:
- CSV2_1: CSV2 to $(DestDataset_CSV2)
- GEODATABASE_FILE_RASTER_DATASET_1: GEODATABASE_FILE_RASTER_DATASET to $(DestDataset_GEODATABASE_FILE_RASTER_DATASET)

PATH (reader PATH_1)
    attributes: path_unix buffer, path_windows buffer, path_rootname buffer, path_filename buffer, path_extension buffer, path_directory_unix buffer, path_directory_windows buffer, path_type char(10)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(path_extension) = csv",CSV,"BOOL_OP,OR,COMPOSITE_TEST,""""""1"""""",TEST_CLAUSE,TEST @Value(path_extension) = tif",TIF
    CSV -> FeatureReader_2 [INITIATOR]
    TIF -> FeatureReader [INITIATOR]
FeatureReader_2
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INTERACT = NONE
    ORDER_RESULTS = No
    OUTPUT_ADD_SCHEMA_ATTRIBUTES = NO
    OUTPUT_FEATURES_DISPLAY = Schema and Data Features
    <OTHER> -> AttributeExposer
AttributeExposer
    ATTR_TABLE = area_id,uint8,day_id,uint16,humidity,real32,month,uint8,rainfall,real32,raster_name,varchar(12),season,uint8,temperature,real32
    -> FeatureJoiner [RIGHT]
FeatureReader
    ATTR_ACCUM_MODE = Merge Initiator and Result
    ATTR_CONFLICT_RES = Use Result
    ATTR_IGNORE_NULLS = No
    COMBINE_GEOM = Use Result
    DATASET = @Value(path_windows)
    FORMAT = GEOTIFF
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    ORDER_RESULTS = No
    OUTPUT_ADD_SCHEMA_ATTRIBUTES = NO
    OUTPUT_FEATURES_DISPLAY = Schema and Data Features
    <OTHER> -> AttributeKeeper
AttributeKeeper
    CREATE_BULK_MODE_FEATURES = NO
    KEEP_ATTRS = path_filename
    -> RasterCellCoercer
RasterCellCoercer
    CELL_GEOMETRY = Polygons
    COL_ATTR = column
    EXTRACT_BAND_VALUES_AS = Attributes
    EXTRACT_NODATA = No
    PRESERVE_ATTRIBUTES = Yes
    ROW_ATTR = row
    -> PythonCaller
PythonCaller
    NEW_ATTRIBUTES = DEM buffer slope buffer VV buffer land_coverage buffer VH buffer area_id buffer
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              lista = [item for item in feature.getAttribute('_band{}.value')]
              st = list(set(lista))
              if not (len(st) == 1 and st[0] == 0):
                  id = feature.getAttribute('path_filename').split(".")[0]
                  id = int(id.split("_")[1])
                  id = id % 19 if id % 19 != 0 else 19
                  feature.setAttribute('DEM', lista[0])
                  feature.setAttribute('slope', round(lista[1],3))
                  feature.setAttribute('VV', lista[2])
                  feature.setAttribute('VH', lista[3])
                  feature.setAttribute('land_coverage', lista[4])
                  feature.setAttribute('area_id', id)
                  self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> Tester
    -> DuplicateFilter_2
Tester
    BOOL_OP = OR
    TEST_CLAUSE = TEST @Value(VV) != -9999
    TEST_MODE = TEST
    PASSED -> FeatureJoiner [LEFT]
FeatureJoiner
    ATTR_CONFLICT_RES = Prefer Left
    GEOMETRY_HANDLING = Prefer Left
    JOIN_KEYS = path_filename raster_name AUTO
    JOIN_MODE = Inner
    JOINED -> AttributeKeeper_2
AttributeKeeper_2
    CREATE_BULK_MODE_FEATURES = NO
    KEEP_ATTRS = DEM,VV,area_id,column,day_id,humidity,land_coverage,month,rainfall,row,season,slope,temperature,VH
    -> Dane_ML (writer CSV2_1)
Dane_ML (writer CSV2_1)
    attributes: column uint32, row uint32, DEM string, slope string, VV string, land_coverage string, VH string, area_id string, day_id uint16, humidity real32, month uint8, rainfall real32, season uint8, temperature real32
Note: Ekstrakcja bazy rastrowej w formie poligonów
DuplicateFilter_2
    INPUT_ORDERED_CHOICE = No
    KEYATTR = area_id column row
    UNIQUE -> 1_FeatureJoiner_2 [LEFT]
Note: Dane tabelaryczne z wyestymowanymi wartościami przez model
CSV (reader CSV2_2)
    attributes: column uint32, row uint32, DEM uint32, slope real32, land_coverage uint32, area_id uint32, day_id uint32, humidity real32, month uint32, rainfall real32, season uint32, temperature real32, VH real64, VV real64
    -> 1_FeatureJoiner_2 [RIGHT]
Note: Łaczenie danych z geometria
1_FeatureJoiner_2: FeatureJoiner
    ATTR_CONFLICT_RES = Prefer Right
    GEOMETRY_HANDLING = Prefer Left
    JOIN_KEYS = column column AUTO row row AUTO area_id area_id AUTO
    JOIN_MODE = Full
    JOINED -> 2_AttributeManager
Note: Usunięcie wartości z klas obszarów innych niż pola/łaki/nieużyki
2_AttributeManager: AttributeManager
    ATTR_TABLE:
      SET_TO VV (buffer) = FME_CONDITIONAL:DEFAULT_VALUE'_FME_NO_OP_'BOOL_OP;OR;COMPOSITE_TEST;1;TEST @Value(land_coverage) NOT_IN 30,40'0'FME_NUM_CONDITIONS2___
      SET_TO VH (buffer) = FME_CONDITIONAL:DEFAULT_VALUE'_FME_NO_OP_'BOOL_OP;OR;COMPOSITE_TEST;1;TEST @Value(land_coverage) NOT_IN 30,40'0'FME_NUM_CONDITIONS2___
    -> 3.1_3DForcer
    -> 3.2_3DForcer_2
Note: Nadanie wysokości poligonom z wyestymowanych zmiennych
3.1_3DForcer: 3DForcer
    KEEPZVAL = No
    ZVALATTR = @Value(VH)
    -> 4.1_PointCloudCombiner
Note: Utworzenie chmury punktów po odpowiednim pogrupowaniu
4.1_PointCloudCombiner: PointCloudCombiner
    ACCUM_ATTRS_NAME = Yes
    EXTRACT_RASTER_NODATA_NAME = No
    GROUP_BY = area_id day_id
    SPACING = 1.0
    -> 5.1_Reprojector
Note: Zamiana układu współrzędnych z katowego na metrowy
5.1_Reprojector: Reprojector
    DEST = ETRS89.PolandCS92
    INTERPOLATION_TYPE_NAME = Nearest Neighbor
    RASTER_CELL_SIZE = Preserve Cells
    RASTER_TOLERANCE = 0.0
    REPROJECTED -> 6.1_NumericRasterizer
Note: Zamiana chmur punktów na rastry o rozdzielczości 10x10m
6.1_NumericRasterizer: NumericRasterizer
    ANTI_ALIASING = No
    BACKGROUND_VALUE = 0
    FILL_WITH_NODATA = Yes
    GROUP_BY = area_id day_id
    INTERPRETATION_TYPE = Real64
    ROWCOL_OR_CELLSIZE = CellSize
    SPECIFY_GROUND_EXTENTS = Use input data ground extents
    TOLERANCE = 0.5
    X_CELL_SIZE = 10
    Y_CELL_SIZE = 10
    RASTER -> 7.1_RasterBandNameSetter
Note: Nadanie nazwy kanałowi przed złaczeniem
7.1_RasterBandNameSetter: RasterBandNameSetter
    BAND_NAME = VH
    INPUT_TYPE = Single Name
    -> 8_RasterBandCombiner
3.2_3DForcer_2: 3DForcer
    KEEPZVAL = No
    ZVALATTR = @Value(VV)
    -> 4.2_PointCloudCombiner_2
4.2_PointCloudCombiner_2: PointCloudCombiner
    ACCUM_ATTRS_NAME = Yes
    EXTRACT_RASTER_NODATA_NAME = No
    GROUP_BY = area_id day_id
    SPACING = 1.0
    -> 5.2_Reprojector_2
5.2_Reprojector_2: Reprojector
    DEST = ETRS89.PolandCS92
    INTERPOLATION_TYPE_NAME = Nearest Neighbor
    RASTER_CELL_SIZE = Preserve Cells
    RASTER_TOLERANCE = 0.0
    REPROJECTED -> 6.2_NumericRasterizer_2
6.2_NumericRasterizer_2: NumericRasterizer
    ANTI_ALIASING = No
    BACKGROUND_VALUE = 0
    FILL_WITH_NODATA = Yes
    GROUP_BY = area_id day_id
    INTERPRETATION_TYPE = Real64
    ROWCOL_OR_CELLSIZE = CellSize
    SPECIFY_GROUND_EXTENTS = Use input data ground extents
    TOLERANCE = 0.5
    X_CELL_SIZE = 10
    Y_CELL_SIZE = 10
    RASTER -> 7.2_RasterBandNameSetter_2
7.2_RasterBandNameSetter_2: RasterBandNameSetter
    BAND_NAME = VV
    INPUT_TYPE = Single Name
    -> 8_RasterBandCombiner
Note: Złaczenie kanałów
8_RasterBandCombiner: RasterBandCombiner
    ACCUM_ATTRS = Use Attributes From One Feature
    GROUP_BY = area_id day_id
    -> 9_RasterExpressionEvaluator [A]
Note: Zamiana obrazów na obrazy binarne
9_RasterExpressionEvaluator: RasterExpressionEvaluator
    EXPRESSION_LIST = AUTO @if(A[0] < -19 && A[1] <-16,1.0,0.0)
    MODE = One Raster
    RESULT -> 10_RasterBandNodataSetter
Note: Ustawienie wartości NoData - zamiana rastrów z typu logicznego na numeryczny
10_RasterBandNodataSetter: RasterBandNodataSetter
    NODATA_VALUE = -9999
    REPLACE_CELL_VALUES = No
    -> 11_RasterBandCombiner_2
Note: Łączenie danych z jednego podobszaru - obraz z 20 kanałami
11_RasterBandCombiner_2: RasterBandCombiner
    ACCUM_ATTRS = Use Attributes From One Feature
    GROUP_BY = area_id
    -> 12_RasterExpressionEvaluator_2 [A]
Note: Sumowanie wartości w kanałach
12_RasterExpressionEvaluator_2: RasterExpressionEvaluator
    EXPRESSION_LIST = AUTO A[0] + A[1] + A[2] + A[3] + A[4] + A[5] + A[6] + A[7] + A[8] + A[9] + A[10] + A[11] + A[12] + A[13] + A[14] + A[15] + A[16] + A[17] + A[18] + A[19]
    MODE = One Raster
    RESULT -> 13_RasterBandNodataSetter_2
Note: Ustawienie wartości NoData na 0 w celu utworzenia przezroczystości na rastrach
13_RasterBandNodataSetter_2: RasterBandNodataSetter
    NODATA_VALUE = 0
    REPLACE_CELL_VALUES = Yes
    -> 14_RasterMosaicker
Note: Złączenie wszystkich podobszarów w mozaikę
14_RasterMosaicker: RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> Winter_low (writer GEODATABASE_FILE_RASTER_DATASET_1)
Note: Eksport rastra do geobazy
Winter_low (writer GEODATABASE_FILE_RASTER_DATASET_1)
    attributes: area_id char(2048), day_id double
DuplicateFilter
    INPUT_ORDERED_CHOICE = No
    KEYATTR = area_id column row
