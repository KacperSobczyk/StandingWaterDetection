FME workspace DaneMeteo.fmw

Parameters:
- SourceDataset_PATH = C:\Users\Kacper.Sobczyk\Downloads\Meteo   # INCLUDE_WEB_BROWSER Source Folder and File Pathnames Folder
- DestDataset_XLSXW = $(FME_MF_DIR)DaneMeteo.xlsx   # Destination Microsoft Excel File
- SourceDataset_GEOJSON_3 = $(FME_MF_DIR)wybrane_obszary.geojson   # Source GeoJSON File or URL
- SourceDataset_GEOJSON = $(FME_MF_DIR)Zestaw-stacji-WGS84.json   # Source GeoJSON File or URL
- DestDataset_GEOJSON = $(FME_MF_DIR)wybrane_obszary_stacje_v2.geojson   # Destination GeoJSON File
- SourceDataset_WFS = https://mapy.geoportal.gov.pl/wss/service/PZGIK/NumerycznyModelTerenuEVRF2007/WFS/Skorowidze   # Source WFS (Web Feature Service) URL
- DestDataset_GEODATABASE_FILE_RASTER_DATASET = $(FME_MF_DIR)RasterData.gdb   # File Geodatabase
- DestDataset_GEOTIFF = C:\Users\Kacper.Sobczyk\Desktop\mgr   # Destination GeoTIFF Folder
- SourceDataset_GEODATABASE_FILE = C:\Users\Kacper.Sobczyk\Documents\ArcGIS\Projects\mgr\Default.gdb   # File Geodatabase

Readers:
- PATH_1: PATH from $(SourceDataset_PATH)
- GEOJSON_1: GEOJSON from $(SourceDataset_GEOJSON)
- GEOJSON_2: GEOJSON from $(SourceDataset_GEOJSON_3)
- WFS_1: WFS from $(SourceDataset_WFS)
- GEODATABASE_FILE_1: GEODATABASE_FILE from $(SourceDataset_GEODATABASE_FILE)

Writers:
- XLSXW_1: XLSXW to $(DestDataset_XLSXW)
- GEOJSON_3: GEOJSON to $(DestDataset_GEOJSON)
- GEODATABASE_FILE_RASTER_DATASET_1: GEODATABASE_FILE_RASTER_DATASET to $(DestDataset_GEODATABASE_FILE_RASTER_DATASET)
- GEOTIFF_1: GEOTIFF to $(DestDataset_GEOTIFF)

obszary (reader GEODATABASE_FILE_1)
    attributes: OBJECTID integer, Shape_Length double, Shape_Area double
    -> Counter
Counter
    CNT_ATTR = OBJECTID
    DOMAIN = counter
    SCOPE = Global
    START = 1
    -> Reprojector_2
Reprojector_2
    DEST = LL-WGS84
    INTERPOLATION_TYPE_NAME = Nearest Neighbor
    RASTER_CELL_SIZE = Preserve Cells
    RASTER_TOLERANCE = 0.0
    REPROJECTED -> NeighborFinder [BASE]
PATH (reader PATH_1)
    attributes: path_unix buffer, path_windows buffer, path_rootname buffer, path_filename buffer, path_extension buffer, path_directory_unix buffer, path_directory_windows buffer, path_type char(10)
    -> Tester
    -> Tester_2
    -> Tester_3
Note: Temperatura
Tester
    BOOL_OP = OR
    TEST_CLAUSE = CASE_INSENSITIVE_TEST @Value(path_rootname) CONTAINS B00300S
    TEST_MODE = TEST
    PASSED -> FeatureReader [INITIATOR]
FeatureReader
    ATTR_ACCUM_MODE = Only Use Result
    COMBINE_GEOM = Use Result
    CSV2_CASE_SENSITIVE_FIELD_NAMES = Yes
    CSV2_CHUNK_SIZE = 100000
    CSV2_DATA_START_LINE = 1
    CSV2_DATE_INPUT_FORMAT = ISO
    CSV2_DELIMITER = ;
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INTERACT = NONE
    ORDER_RESULTS = No
    OUTPUT_ADD_SCHEMA_ATTRIBUTES = NO
    OUTPUT_FEATURES_DISPLAY = Schema and Data Features
    <OTHER> -> AttributeExposer
AttributeExposer
    ATTR_LIST = col0,col1,col2,col3,col4
    -> Tester_4
Tester_4
    BOOL_OP = OR
    TEST_CLAUSE = TEST @Value(col0) IN 250200210,250200220,250200250,250200280
    TEST_MODE = TEST
    PASSED -> AttributeRenamer
    PASSED -> DuplicateFilter
DuplicateFilter
    INPUT_ORDERED_CHOICE = No
    KEYATTR = col0
AttributeRenamer
    ATTR_TABLE:
      RENAME_SET_DEFAULT col0 > Station ID
      RENAME_SET_DEFAULT col1 > FileType ID
      RENAME_SET_DEFAULT col2 > Datetime
      RENAME_SET_DEFAULT col3 > Temperature
    KEEP_RENAMED_ONLY = no
    MISSING_INPUT_ATTRS = REMOVE
    -> PythonCaller
PythonCaller
    HIDE_ATTRIBUTES = col4
    NEW_ATTRIBUTES = Year Month Day Time
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              attr_date, time = feature.getAttribute('Datetime').split()
              year, month, day = attr_date.split('-')
              new_datetime = feature.getAttribute('Datetime').replace(" ", "")
              new_datetime = new_datetime.replace("-", "")
              new_datetime = new_datetime.replace(":", "")
              feature.setAttribute('Datetime',new_datetime + "00")
              feature.setAttribute("Year", year)
              feature.setAttribute("Month", month)
              feature.setAttribute("Day", day)
              feature.setAttribute("Time", time)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> Tester_7
Tester_7
    BOOL_OP = OR
    TEST_CLAUSE = TEST @Value(Time) = 16:00
    TEST_MODE = TEST
    PASSED -> Tester_8
Tester_8
    BOOL_OP = OR
    TEST_CLAUSE = TEST @Value(Datetime) != 20240630160000
    TEST_MODE = TEST
    PASSED -> AttributeKeeper_3
AttributeKeeper_3
    CREATE_BULK_MODE_FEATURES = NO
    KEEP_ATTRS = Day,Month,Station ID,Year,Temperature
    -> FeatureJoiner [LEFT]
Note: Opady (dzien poprzedni i noc)
Tester_2
    BOOL_OP = OR
    TEST_CLAUSE = CASE_INSENSITIVE_TEST @Value(path_rootname) CONTAINS B00604S
    TEST_MODE = CASE_INSENSITIVE_TEST
    PASSED -> FeatureReader_2 [INITIATOR]
FeatureReader_2
    ATTR_ACCUM_MODE = Only Use Result
    COMBINE_GEOM = Use Result
    CSV2_CASE_SENSITIVE_FIELD_NAMES = Yes
    CSV2_CHUNK_SIZE = 100000
    CSV2_DATA_START_LINE = 1
    CSV2_DATE_INPUT_FORMAT = ISO
    CSV2_DELIMITER = ;
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 0
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INTERACT = NONE
    ORDER_RESULTS = No
    OUTPUT_ADD_SCHEMA_ATTRIBUTES = NO
    OUTPUT_FEATURES_DISPLAY = Schema and Data Features
    <OTHER> -> AttributeExposer_2
AttributeExposer_2
    ATTR_LIST = col0,col1,col2,col3,col4
    -> Tester_5
Tester_5
    BOOL_OP = OR
    TEST_CLAUSE = TEST @Value(col0) IN 250200210,250200220,250200250,250200280
    TEST_MODE = TEST
    PASSED -> AttributeRenamer_2
AttributeRenamer_2
    ATTR_TABLE:
      RENAME_SET_DEFAULT col0 > Station ID
      RENAME_SET_DEFAULT col1 > FileType ID
      RENAME_SET_DEFAULT col2 > Datetime
      RENAME_SET_DEFAULT col3 > Rainfall
    KEEP_RENAMED_ONLY = no
    MISSING_INPUT_ATTRS = REMOVE
    -> PythonCaller_2
PythonCaller_2
    HIDE_ATTRIBUTES = col4
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              new_datetime = feature.getAttribute('Datetime').replace(" ", "")
              new_datetime = new_datetime.replace("-", "")
              new_datetime = new_datetime.replace(":", "")
              feature.setAttribute('Datetime',new_datetime + "00")
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> DateTimeCalculator
DateTimeCalculator
    MODE = DATETIMECALC_1_ADD_INTERVAL
    OPERATION_PARAMETERS = START_DATETIME]@Value(Datetime)]OPERATOR]SUBTRACT]YEARS]0]MONTHS]0]DAYS]1]HOURS]0]MINUTES]0]SECONDS]0]RESULT_DATETIME]NewDatetime]FME_CONTROLLER_QUERY_FILE]transformers/dependencies/datetimecalculator/DATETIMECALC_1_ADD_INTERVAL.fme]FME_CONTROLLER_CHOICE]DATETIMECALC_1_ADD_INTERVAL
    -> PythonCaller_3
PythonCaller_3
    NEW_ATTRIBUTES = Year Month Day
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              feature.setAttribute("Year", str(feature.getAttribute('NewDatetime'))[0:4])
              feature.setAttribute("Month", str(feature.getAttribute('NewDatetime'))[4:6])
              feature.setAttribute("Day", str(feature.getAttribute('NewDatetime'))[6:8])
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> Tester_6
Tester_6
    BOOL_OP = OR
    TEST_CLAUSE = TEST @Value(Year) != 2020
    TEST_MODE = TEST
    PASSED -> AttributeKeeper_2
AttributeKeeper_2
    CREATE_BULK_MODE_FEATURES = NO
    KEEP_ATTRS = Day,Month,Station ID,Year,Rainfall
    -> FeatureJoiner [RIGHT]
FeatureJoiner
    ATTR_CONFLICT_RES = Prefer Left
    GEOMETRY_HANDLING = Prefer Left
    JOIN_KEYS = Day Day AUTO Month Month AUTO Year Year AUTO Station ID Station ID AUTO
    JOIN_MODE = Inner
    JOINED -> Junction
    UNJOINED_LEFT -> Junction
Junction
    -> FeatureJoiner_2 [LEFT]
Note: Wilgotnosc względna powietrza
Tester_3
    BOOL_OP = OR
    TEST_CLAUSE = CASE_INSENSITIVE_TEST @Value(path_rootname) CONTAINS B00802A
    TEST_MODE = TEST
    PASSED -> FeatureReader_3 [INITIATOR]
FeatureReader_3
    ATTR_ACCUM_MODE = Only Use Result
    COMBINE_GEOM = Use Result
    CSV2_CASE_SENSITIVE_FIELD_NAMES = Yes
    CSV2_CHUNK_SIZE = 100000
    CSV2_DATA_START_LINE = 1
    CSV2_DATE_INPUT_FORMAT = ISO
    CSV2_DELIMITER = ;
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 0
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INTERACT = NONE
    ORDER_RESULTS = No
    OUTPUT_ADD_SCHEMA_ATTRIBUTES = NO
    OUTPUT_FEATURES_DISPLAY = Schema and Data Features
    <OTHER> -> AttributeExposer_3
AttributeExposer_3
    ATTR_LIST = col0,col1,col2,col3,col4
    -> Tester_9
Tester_9
    BOOL_OP = OR
    TEST_CLAUSE = TEST @Value(col0) IN 250200210,250200220,250200250,250200280
    TEST_MODE = TEST
    PASSED -> AttributeRenamer_3
AttributeRenamer_3
    ATTR_TABLE:
      RENAME_SET_DEFAULT col0 > Station ID
      RENAME_SET_DEFAULT col1 > FileType ID
      RENAME_SET_DEFAULT col2 > Datetime
      RENAME_SET_DEFAULT col3 > Humidity
    KEEP_RENAMED_ONLY = no
    MISSING_INPUT_ATTRS = REMOVE
    -> PythonCaller_4
PythonCaller_4
    HIDE_ATTRIBUTES = col4
    NEW_ATTRIBUTES = Year Month Day Time
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              attr_date, time = feature.getAttribute('Datetime').split()
              year, month, day = attr_date.split('-')
              new_datetime = feature.getAttribute('Datetime').replace(" ", "")
              new_datetime = new_datetime.replace("-", "")
              new_datetime = new_datetime.replace(":", "")
              feature.setAttribute('Datetime',new_datetime + "00")
              feature.setAttribute("Year", year)
              feature.setAttribute("Month", month)
              feature.setAttribute("Day", day)
              feature.setAttribute("Time", time)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> Tester_10
Tester_10
    BOOL_OP = OR
    TEST_CLAUSE = TEST @Value(Time) = 16:00
    TEST_MODE = TEST
    PASSED -> Tester_11
Tester_11
    BOOL_OP = OR
    TEST_CLAUSE = TEST @Value(Datetime) != 20240630160000
    TEST_MODE = TEST
    PASSED -> AttributeKeeper
AttributeKeeper
    CREATE_BULK_MODE_FEATURES = NO
    KEEP_ATTRS = Day,Humidity,Month,Station ID,Year
    -> FeatureJoiner_2 [RIGHT]
FeatureJoiner_2
    ATTR_CONFLICT_RES = Prefer Left
    GEOMETRY_HANDLING = Prefer Left
    JOIN_KEYS = Day Day AUTO Month Month AUTO Year Year AUTO Station ID Station ID AUTO
    JOIN_MODE = Inner
    JOINED -> Junction_2
    UNJOINED_RIGHT -> Junction_2
Junction_2
    -> Sorter
Sorter
    SORT_PARM = Year NATURAL ASCENDING Month NATURAL ASCENDING Day NATURAL ASCENDING
    SORTED -> DATA (writer XLSXW_1)
DATA (writer XLSXW_1)
    attributes: Station ID string(20), Year string(20), Month string(20), Day string(20), Temperature string(20), Rainfall string(20), Humidity string(20)
Stacje (reader GEOJSON_1)
    attributes: LP. int, ID int, Nazwa string, Województwo string, Powiat string
    -> Tester_12
Tester_12
    BOOL_OP = OR
    TEST_CLAUSE = TEST @Value(ID) IN 250200210,250200220,250200280
    TEST_MODE = TEST
    PASSED -> NeighborFinder [CANDIDATE]
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> AttributeKeeper_4
AttributeKeeper_4
    CREATE_BULK_MODE_FEATURES = NO
    KEEP_ATTRS = ID,OBJECTID
    -> AttributeRenamer_4
AttributeRenamer_4
    ATTR_TABLE = RENAME_SET_DEFAULT ID > Station_ID
    KEEP_RENAMED_ONLY = no
    MISSING_INPUT_ATTRS = REMOVE
    -> 2DForcer
2DForcer
    2D -> Obszary (writer GEOJSON_3)
Obszary (writer GEOJSON_3)
    attributes: Station_ID int, OBJECTID int
Obszar (reader GEOJSON_2)
    attributes: OBJECTID int, Shape_Length float, Shape_Area float
    -> Reprojector
Reprojector
    DEST = ETRS89.PolandCS92
    INTERPOLATION_TYPE_NAME = Nearest Neighbor
    RASTER_CELL_SIZE = Preserve Cells
    RASTER_TOLERANCE = 0.0
    REPROJECTED -> SpatialFilter [Filter]
    REPROJECTED -> Clipper [CLIPPER]
SkorowidzNMT2023 (reader WFS_1)
    attributes: gml_parent_id xml_buffer, gml_parent_property xml_buffer, gml_id xml_buffer, msGeometry xml_geometry, godlo xml_buffer, akt_rok xml_int64, asortyment xml_buffer, format xml_buffer, char_przestrz xml_buffer, blad_sr_wys xml_real64, uklad_xy xml_buffer, modul_archiwizacji xml_buffer, uklad_h xml_buffer, nr_zglosz xml_buffer, akt_data xml_date, czy_ark_wypelniony xml_buffer, url_do_pobrania xml_buffer, zrodlo_danych xml_buffer, dt_pzgik xml_date, blad_sr_syt xml_real64
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Tester_13
Tester_13
    BOOL_OP = OR
    TEST_CLAUSE = TEST @Value(uklad_xy) = PL-1992
    TEST_MODE = TEST
    PASSED -> FeatureReader_4 [INITIATOR]
FeatureReader_4
    ATTR_ACCUM_MODE = Only Use Result
    COMBINE_GEOM = Use Result
    DATASET = @Value(url_do_pobrania)
    ESRIASCIIGRID_GROUP_BY_DATASET = No
    ESRIASCIIGRID_READER_META_ATTRIBUTES = fme_basename
    ESRIASCIIGRID_USE_SEARCH_ENVELOPE = NO
    FORMAT = ESRIASCIIGRID
    INTERACT = NONE
    ORDER_RESULTS = No
    OUTPUT_ADD_SCHEMA_ATTRIBUTES = NO
    OUTPUT_FEATURES_DISPLAY = Schema and Data Features
    <OTHER> -> CoordinateSystemSetter
CoordinateSystemSetter
    COORDSYS = ETRS89.PolandCS92
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> Clipper [CANDIDATE]
Clipper
    ADD_NODATA = YES
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> NMT (writer GEODATABASE_FILE_RASTER_DATASET_1)
    INSIDE -> RasterSlopeCalculator
NMT (writer GEODATABASE_FILE_RASTER_DATASET_1)
    attributes: ID bigint
RasterSlopeCalculator
    ALGORITHM = Horn
    INTERPOLATE_NODATA = Yes
    OUTPUT_TYPE = Degrees
    -> SLOPE (writer GEODATABASE_FILE_RASTER_DATASET_1)
    -> NMT (writer GEOTIFF_1)
NMT (writer GEOTIFF_1)
    attributes: ID largeint
SLOPE (writer GEODATABASE_FILE_RASTER_DATASET_1)
    attributes: ID bigint
